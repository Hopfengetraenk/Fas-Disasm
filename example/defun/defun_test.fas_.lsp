(defun main 
;; FasStringtables 0
;; FasStringtables 1
(defun main 
nil
(princ "Start")
testext
local
test
(test 1 2)
(princ "End") )
(defun testext (blah1  blah2)
(princ "Start") )
(defun local(/ blah1 blah2)
(defun local(/ blah1 blah2)
(princ "Start") )
(defun test (blah1  blah2 / ang1 ang2)
(defun test (blah1  blah2 / ang1 ang2)
(princ (strcat "\nANG1 has the value " ang1))
(princ (strcat "\nANG2 has the value " ang2))
(princ )
(defun ddsteel(/ p1 p2 p3)
(defun ddsteel(/ p1 p2 p3)
(princ "func Inside func") )
ddsteel )
